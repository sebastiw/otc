MAP-OTC {
   otc(68) identified-organization(4) etsi(0) mobileDomain(0)
   gsm-Network(1) modules(3) map-Protocol(4) version9(9)}

DEFINITIONS
IMPLICIT TAGS
::=
BEGIN

IMPORTS
   TCMessage{}
FROM TCAPMessages {
   ccitt recommendation q 773 modules(2) messages(1) version3(3)}

  Supported-MAP-Operations
FROM MAP-Protocol {itu-t identified-organization (4) etsi (0) mobileDomain (0)
  gsm-Network (1) modules (3) map-Protocol (4) version9 (9)}
;

MapSpecificPDUs ::=
   TCMessage {{Supported-MAP-Operations}, {Supported-MAP-Operations}}

END
